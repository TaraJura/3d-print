# -*- coding: utf-8 -*-
"""Parametrický prototyp držáku role s odkládací schránkou (mm).

Spuštění přepíše výstupní FCStd, pět STL a kontrolní JSON v této složce.
Neodesílá nic do sliceru ani do tiskárny. Fotografie nemá měřítko: všechny
rozměry jsou návrhové. V tabulce Parameters lze měnit hlavní hodnoty bez
tohoto makra; dokument používá jen standardní objekty, booleany a výrazy.
"""
from pathlib import Path
import hashlib
import json
import FreeCAD as App
import Part
import MeshPart

OUT = Path(__file__).resolve().parent
STL = OUT / "stl"
STL.mkdir(exist_ok=True)

VALUES = [
    ("BodyWidth", "Šířka schránky", 190, "návrh z fotografie"),
    ("BodyDepth", "Hloubka schránky", 120, "návrh z fotografie"),
    ("BodyHeight", "Výška schránky", 58, "návrh z fotografie"),
    ("OuterRadius", "Zaoblení rohů", 14, "návrh"),
    ("Wall", "Boční a čelní stěna", 4, "návrh"),
    ("BackWall", "Zadní stěna", 5, "návrh"),
    ("Floor", "Dno schránky", 5, "návrh"),
    ("LidThickness", "Víko – deska", 4, "návrh"),
    ("LidLipHeight", "Víko – zasouvací lem", 5, "návrh"),
    ("LidLipWall", "Víko – tloušťka lemu", 2.5, "návrh"),
    ("LidClearance", "Vůle lemu na stranu", 0.5, "návrh; ověřit tiskem"),
    ("FingerNotchRadius", "Úchop víka – poloměr", 12, "návrh"),
    ("BracketThickness", "Tloušťka ramene", 12, "návrh"),
    ("BracketLength", "Délka ramene", 88, "návrh"),
    ("BracketHeight", "Výška ramene", 91, "návrh"),
    ("BracketInsetX", "Odsazení ramen od boku", 25, "návrh"),
    ("BracketOffsetY", "Odsazení ramen od stěny", 20, "návrh"),
    ("BracketScrewDia", "Montážní otvor M4", 4.6, "návrh; šrouby ověřit"),
    ("WallScrewDia", "Otvor pro uchycení ke stěně", 5.5, "návrh; kotvy dle podkladu"),
    ("AxleRadius", "Poloměr osy role", 6, "návrh"),
    ("AxleLength", "Délka těla osy", 148, "návrh"),
    ("AxleHeadRadius", "Poloměr hlavy osy", 10, "návrh"),
    ("AxleHeadLength", "Tloušťka hlavy osy", 4, "návrh"),
    ("CapOuterRadius", "Poloměr zátky", 10, "návrh"),
    ("CapSocketRadius", "Poloměr otvoru zátky", 6.05, "návrh; vyzkoušet fit"),
    ("CapHeight", "Výška zátky", 8, "návrh"),
]

doc = App.newDocument("DrzakToaletnihoPapiru")
doc.Label = "Držák toaletního papíru s přihrádkou – tiskový prototyp"
sheet = doc.addObject("Spreadsheet::Sheet", "Parameters")
sheet.Label = "Parametry – všechny délky v mm"
for col, value in zip("ABC", ("Parametr", "Hodnota", "Původ")):
    sheet.set(col + "1", value)
sheet.setStyle("A1:C1", "bold", "add")
sheet.setBackground("A1:C1", (0.83, 0.89, 0.94))
for row, (alias, label, value, status) in enumerate(VALUES, 2):
    sheet.set(f"A{row}", label)
    sheet.set(f"B{row}", f"{value:g} mm")
    sheet.setAlias(f"B{row}", alias)
    sheet.set(f"C{row}", status)
    sheet.setBackground(f"B{row}", (1.0, 0.94, 0.79))
sheet.setColumnWidth("A", 320)
sheet.setColumnWidth("B", 125)
sheet.setColumnWidth("C", 260)
doc.recompute()

def p(alias):
    return "Parameters." + alias

def e(obj, prop, value):
    obj.setExpression(prop, value)

def box(name, label, length, width, height, x="0 mm", y="0 mm", z="0 mm"):
    obj = doc.addObject("Part::Box", name)
    obj.Label = label
    for prop, val in zip(("Length", "Width", "Height"), (length, width, height)):
        e(obj, prop, val)
    for prop, val in zip(("x", "y", "z"), (x, y, z)):
        e(obj, "Placement.Base." + prop, val)
    return obj

def cylinder(name, label, radius, height, x, y, z, rotation=None):
    obj = doc.addObject("Part::Cylinder", name)
    obj.Label = label
    e(obj, "Radius", radius)
    e(obj, "Height", height)
    if rotation is not None:
        obj.Placement.Rotation = rotation
    for prop, val in zip(("x", "y", "z"), (x, y, z)):
        e(obj, "Placement.Base." + prop, val)
    return obj

def fuse(name, label, shapes):
    obj = doc.addObject("Part::MultiFuse", name)
    obj.Label = label
    obj.Shapes = shapes
    obj.Refine = True
    return obj

def cut(name, label, base, tool):
    obj = doc.addObject("Part::Cut", name)
    obj.Label = label
    obj.Base = base
    obj.Tool = tool
    obj.Refine = True
    return obj

def rounded_prism(prefix, label, w, d, r, h, x, y, z):
    """Zaoblený obdélníkový hranol ze standardních parametrických těles."""
    parts = [
        box(prefix + "CoreA", label + " / střed A", f"{w} - 2*({r})", d, h,
            f"{x} + {r}", y, z),
        box(prefix + "CoreB", label + " / střed B", w, f"{d} - 2*({r})", h,
            x, f"{y} + {r}", z),
    ]
    for i, xx in enumerate((f"{x} + {r}", f"{x} + {w} - {r}")):
        for j, yy in enumerate((f"{y} + {r}", f"{y} + {d} - {r}")):
            parts.append(cylinder(prefix + f"Round{i}{j}", label + " / roh", r, h, xx, yy, z))
    return fuse(prefix, label, parts)

W, D, H, R = (p("BodyWidth"), p("BodyDepth"), p("BodyHeight"), p("OuterRadius"))
wall, back, floor = (p("Wall"), p("BackWall"), p("Floor"))
inner_w = f"{W} - 2*{wall}"
inner_d = f"{D} - {back} - {wall}"
inner_r = f"{R} - {wall}"

# Tělo: vrch otevřený, dno a montážní otvory v zadní stěně a dnu.
outer = rounded_prism("BodyOuter", "Vnější obrys schránky", W, D, R, H, "0 mm", "0 mm", "0 mm")
inner = rounded_prism("BodyCavity", "Vnitřní prostor schránky", inner_w, inner_d,
                      inner_r, f"{H} + 2 mm", wall, back, floor)
shell = cut("BodyShell", "Dutá schránka", outer, inner)
wall_holes = []
for n, x in enumerate((f"{W}/2 - 65 mm", f"{W}/2 + 65 mm"), 1):
    wall_holes.append(cylinder(f"WallHole{n}", f"Otvor do stěny {n}",
                               f"{p('WallScrewDia')}/2", f"{back} + 2 mm",
                               x, f"{back} + 1 mm", "34 mm",
                               App.Rotation(App.Vector(1, 0, 0), 90)))
shell = cut("BodyWallMounted", "Schránka / otvory do stěny", shell,
            fuse("WallHoles", "Dva montážní otvory", wall_holes))
bracket_xs = (f"{p('BracketInsetX')} + {p('BracketThickness')}/2",
              f"{W} - {p('BracketInsetX')} - {p('BracketThickness')}/2")
attach_holes = []
for i, x in enumerate(bracket_xs, 1):
    for j, y in enumerate((f"{p('BracketOffsetY')} + 30 mm",
                           f"{p('BracketOffsetY')} + 76 mm"), 1):
        attach_holes.append(cylinder(f"AttachHole{i}{j}", f"Otvor ramene {i}.{j}",
                                     f"{p('BracketScrewDia')}/2", f"{floor} + 2 mm",
                                     x, y, "-1 mm"))
body = cut("Body", "Schránka – výsledný tiskový díl", shell,
           fuse("AttachHoles", "Čtyři otvory pro ramena", attach_holes))

# Víko: rovná vnější strana leží při tisku na podložce, dovnitř vystupuje lem.
lid_top = rounded_prism("LidTop", "Horní deska víka", W, D, R,
                        p("LidThickness"), "0 mm", "0 mm", "0 mm")
lip_w = f"{inner_w} - 2*{p('LidClearance')}"
lip_d = f"{inner_d} - 2*{p('LidClearance')}"
lip_r = f"{inner_r} - {p('LidClearance')}"
lip_x = f"{wall} + {p('LidClearance')}"
lip_y = f"{back} + {p('LidClearance')}"
lip_outer = rounded_prism("LidLipOuter", "Vnější obrys lemu", lip_w, lip_d,
                          lip_r, p("LidLipHeight"), lip_x, lip_y, p("LidThickness"))
lip_inner = rounded_prism("LidLipInner", "Vnitřní obrys lemu",
                          f"{lip_w} - 2*{p('LidLipWall')}",
                          f"{lip_d} - 2*{p('LidLipWall')}",
                          f"{lip_r} - {p('LidLipWall')}",
                          f"{p('LidLipHeight')} + 2 mm",
                          f"{lip_x} + {p('LidLipWall')}",
                          f"{lip_y} + {p('LidLipWall')}",
                          f"{p('LidThickness')} - 1 mm")
lip = cut("LidLip", "Zasouvací lem", lip_outer, lip_inner)
lid_raw = fuse("LidRaw", "Deska a lem", [lid_top, lip])
finger = cylinder("FingerNotch", "Půlkruhový úchop víka",
                  p("FingerNotchRadius"), f"{p('LidThickness')} + {p('LidLipHeight')} + 2 mm",
                  f"{W}/2", f"{D} + 2 mm", "-1 mm")
lid = cut("Lid", "Snímatelné víko – výsledný tiskový díl", lid_raw, finger)

# Obě ramena jsou fyzicky stejné výtisky. Dolní pás je na plocho ve směru vrstev.
bt, bl, bh = (p("BracketThickness"), p("BracketLength"), p("BracketHeight"))
bracket_parts = [
    box("BracketTop", "Horní montážní pás", bt, bl, "12 mm", "0 mm", "0 mm", f"{bh} - 12 mm"),
    box("BracketBack", "Zadní stojina", bt, "16 mm", f"{bh} - 12 mm"),
    box("BracketArm", "Dolní nosné rameno", bt, "76 mm", "12 mm"),
    box("BracketStopBack", "Zadní zarážka osy", bt, "6 mm", "8 mm", "0 mm", "47 mm", "12 mm"),
    box("BracketStopFront", "Přední zarážka osy", bt, "7 mm", "8 mm", "0 mm", "69 mm", "12 mm"),
]
bracket_raw = fuse("BracketRaw", "Rameno / pevný profil", bracket_parts)
bracket_holes = [cylinder(f"BracketBolt{j}", f"Montážní otvor M4 / {j}",
                          f"{p('BracketScrewDia')}/2", "14 mm", f"{bt}/2", f"{yy} mm",
                          f"{bh} - 13 mm") for j, yy in enumerate((30, 76), 1)]
bracket = cut("Bracket", "Boční rameno – tisknout 2×", bracket_raw,
              fuse("BracketHoles", "Otvory v rameni", bracket_holes))

# Osa se zploštěnou tiskovou plochou: žádná podpora pod dlouhým válcem.
shaft_core = cylinder("AxleCore", "Osa Ø12", p("AxleRadius"), p("AxleLength"),
                      p("AxleHeadLength"), "0 mm", p("AxleRadius"),
                      App.Rotation(App.Vector(0, 1, 0), 90))
shaft_head = cylinder("AxleHead", "Hlava osy", p("AxleHeadRadius"), p("AxleHeadLength"),
                      "0 mm", "0 mm", p("AxleRadius"),
                      App.Rotation(App.Vector(0, 1, 0), 90))
shaft_round = fuse("AxleRound", "Osa s hlavou", [shaft_core, shaft_head])
shaft_flat_box = box("AxleFlatTool", "Plocha pro tisk", f"{p('AxleLength')} + {p('AxleHeadLength')} + 2 mm",
                     "22 mm", "17 mm", "-1 mm", "-11 mm", "1.5 mm")
shaft = doc.addObject("Part::Common", "Axle")
shaft.Label = "Vyjímatelná osa – výsledný tiskový díl"
shaft.Base = shaft_round
shaft.Tool = shaft_flat_box
shaft.Refine = True

# Prstencová nasazovací zátka, otevřená drážka dovoluje jemný pružný stisk.
cap_outer = cylinder("CapOuter", "Zátka / obvod", p("CapOuterRadius"), p("CapHeight"),
                     "10 mm", "10 mm", "0 mm")
cap_socket = cylinder("CapSocket", "Zátka / otvor", p("CapSocketRadius"),
                      f"{p('CapHeight')} - 1 mm", "10 mm", "10 mm", "2 mm")
cap_cup = cut("CapCup", "Zátka / dutina", cap_outer, cap_socket)
cap_slit = box("CapSlit", "Pružná štěrbina zátky", "12 mm", "2.5 mm",
               f"{p('CapHeight')} + 2 mm", "10 mm", "8.75 mm", "-1 mm")
cap = cut("Cap", "Pružná pojistná zátka – výsledný tiskový díl", cap_cup, cap_slit)

finals = [body, lid, bracket, shaft, cap]
doc.recompute()
report = {"status": "geometrie CAD; fyzický tisk a montáž neověřeny",
          "source_sha256": hashlib.sha256(Path(__file__).read_bytes()).hexdigest(),
          "parameters_mm": {a: v for a, _, v, _ in VALUES},
          "pieces": {"Body": 1, "Lid": 1, "Bracket": 2, "Axle": 1, "Cap": 1},
          "parts": {}}
for obj in finals:
    if not obj.Shape.isValid() or len(obj.Shape.Solids) != 1:
        raise RuntimeError(f"Invalid {obj.Name}: {obj.State}, solids={len(obj.Shape.Solids)}")
    bb = obj.Shape.BoundBox
    # STL jsou v orientaci na podložce; otočena jsou jen obě stejná ramena.
    mesh_shape = obj.Shape.copy()
    if obj == bracket:
        mesh_shape.rotate(App.Vector(0, 0, 0), App.Vector(0, 1, 0), -90)
    bbm = mesh_shape.BoundBox
    mesh_shape.translate(App.Vector(-bbm.XMin, -bbm.YMin, -bbm.ZMin))
    mesh = MeshPart.meshFromShape(Shape=mesh_shape, LinearDeflection=0.08,
                                  AngularDeflection=0.15, Relative=False)
    target = STL / (obj.Name.lower() + ".stl")
    mesh.write(str(target))
    if not mesh.isSolid():
        raise RuntimeError(f"Open STL mesh: {target}")
    printable = mesh_shape.BoundBox
    report["parts"][obj.Name] = {
        "solid_count": len(obj.Shape.Solids), "cad_valid": obj.Shape.isValid(),
        "cad_dimensions_mm": [bb.XLength, bb.YLength, bb.ZLength],
        "print_dimensions_mm": [printable.XLength, printable.YLength, printable.ZLength],
        "volume_mm3": obj.Shape.Volume, "stl_facets": mesh.CountFacets,
        "stl_closed": mesh.isSolid(), "stl": str(target.relative_to(OUT))}

# Názorná sestava v jednom FCStd. Vazby jsou standardní App::Link a výrazy.
def link(name, label, source, rotation, xyz):
    obj = doc.addObject("App::Link", name)
    obj.Label = label
    obj.LinkedObject = source
    obj.Placement.Rotation = rotation
    for axis, expression in zip("xyz", xyz):
        e(obj, "Placement.Base." + axis, expression)
    return obj

assembled = [
    link("AssemblyBody", "Sestava / schránka", body, App.Rotation(),
         ("0 mm", "0 mm", "0 mm")),
    link("AssemblyLid", "Sestava / nasazené víko", lid,
         App.Rotation(App.Vector(1, 0, 0), 180),
         ("0 mm", D, f"{H} + {p('LidThickness')}")),
    link("AssemblyBracketLeft", "Sestava / levé rameno", bracket, App.Rotation(),
         (p("BracketInsetX"), p("BracketOffsetY"), f"-{p('BracketHeight')}")),
    link("AssemblyBracketRight", "Sestava / pravé rameno", bracket, App.Rotation(),
         (f"{W} - {p('BracketInsetX')} - {p('BracketThickness')}",
          p("BracketOffsetY"), f"-{p('BracketHeight')}")),
    link("AssemblyAxle", "Sestava / osa role", shaft, App.Rotation(),
         (f"{p('BracketInsetX')} - 5 mm",
          f"{p('BracketOffsetY')} + 61 mm",
          f"-{p('BracketHeight')} + 18 mm - {p('AxleRadius')}")),
    link("AssemblyCap", "Sestava / zátka osy", cap,
         App.Rotation(App.Vector(0, 1, 0), -90),
         (f"{p('BracketInsetX')} - 5 mm + {p('AxleHeadLength')} + {p('AxleLength')} + 2 mm",
          f"{p('BracketOffsetY')} + 61 mm - 10 mm",
          f"-{p('BracketHeight')} + 18 mm - 10 mm")),
]
doc.recompute()
for obj in assembled:
    if "Invalid" in obj.State or obj.Shape.isNull():
        raise RuntimeError(f"Invalid assembly link {obj.Name}: {obj.State}")

if App.GuiUp:
    import FreeCADGui as Gui
    for obj in doc.Objects:
        if hasattr(obj, "ViewObject"):
            obj.ViewObject.Visibility = obj in assembled
    for obj, rgb in zip(finals, ((0.19, 0.21, 0.25), (0.29, 0.31, 0.35),
                                 (0.19, 0.21, 0.25), (0.35, 0.37, 0.40),
                                 (0.35, 0.37, 0.40))):
        obj.ViewObject.ShapeColor = rgb
        obj.ViewObject.LineColor = (0.08, 0.08, 0.09)
    Gui.activeDocument().activeView().viewAxonometric()
    Gui.activeDocument().activeView().fitAll()

doc.saveAs(str(OUT / "drzak.FCStd"))
(OUT / "kontrola-modelu.json").write_text(json.dumps(report, indent=2, ensure_ascii=False) + "\n")
print("CAD_EXPORT_OK", json.dumps({k: v["print_dimensions_mm"] for k, v in report["parts"].items()}), flush=True)
