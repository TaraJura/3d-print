# -*- coding: utf-8 -*-
"""Revision03: 575mm installation, three TPU95A snap bodies. Native FreeCAD.
Regeneration overwrites ONLY artifacts beside this macro: FCStd, STL and auditJSON.
No printer operation. Bed and end-seal reference shapes are never exported.
"""
from pathlib import Path
import json,math
import FreeCAD as App
import Part,Sketcher,MeshPart
OUT=Path(__file__).resolve().parent
for name in ('stl','vzorek'): (OUT/name).mkdir(exist_ok=True)
VALUES=[
 ('TotalLength','Celková instalace včetně konců',575,'ZADÁNO 23.9.2026'),
 ('Width','Celková šířka MAX20',20,'ZADÁNO; fyzická tolerance neověřená'),
 ('Height','Výška TPU',8,'ZACHOVANÝ NÁVRH'),
 ('Bed','Lepicí lože pod lištou',2,'ZACHOVAT; není lepidlem uvnitř spojů'),
 ('EndSeal','Rezerva na každém konci',2,'ZACHOVANÝ NÁVRH uvnitř575'),
 ('NoseRadius','Poloměr nízkého náběhu',0.5,'ZACHOVANÝ PROFIL B'),
 ('BackRadius','Poloměr vysokého ramene',3,'ZACHOVANÝ PROFIL B'),
 ('SnapY','Osa západky od nízké strany',13,'NÁVRH'),
 ('Neck','Šířka krčku u paty',5.6,'NÁVRH'),
 ('Head','Šířka západky u paty',7.2,'NÁVRH'),
 ('Shoulder','Poloha zadržovacího ramene',12,'NÁVRH od čela'),
 ('TipLength','Přesah vidlice',18,'NÁVRH'),
 ('Slot','Pružná středová štěrbina',2,'NÁVRH'),
 ('RootBack','Kořen štěrbiny za čelem',4,'NÁVRH; zaoblení R Slot/2'),
 ('Clearance','Vnitřní vůle na stranu',0.2,'NÁVRH; neověřeno tiskem'),
 ('Taper','Zachycení Z: zúžení na stranu',0.6,'NÁVRH'),
 ('TaperHeight','Výška poloviny dvojité rybiny',1.2,'NÁVRH; sklon26.6 stupne od svislice'),
 ('GuideLength','Délka druhého vodicího pera',5,'NÁVRH; prodlouží styčnou cestu'),
 ('GuideY','Začátek druhého pera v šířce',2,'NÁVRH'),
 ('GuideWidth','Šířka druhého pera',3,'NÁVRH'),
 ('RootRadius','Vnější zaoblení kořene vidlice',1,'NÁVRH; oblouk8sektory, odchylka<0.005mm'),
]
doc=App.newDocument('Prepazka575Snap');doc.Label='Přepážka B575 — zacvakávací revize03 — návrh'
sheet=doc.addObject('Spreadsheet::Sheet','Parameters')
sheet.Label='Parametry v mm — návrhový fit není fyzicky ověřen'
for c,v in [('A1','Parametr'),('B1','Hodnota'),('C1','Původ')]:sheet.set(c,v)
for row,(alias,label,val,status) in enumerate(VALUES,2):
 sheet.set(f'A{row}',label);sheet.set(f'B{row}',f'{val} mm');sheet.setAlias(f'B{row}',alias);sheet.set(f'C{row}',status)
for row,alias,formula in [(30,'Pitch','(TotalLength - 2 * EndSeal) / 3'),(31,'Joint1','EndSeal + Pitch'),(32,'Joint2','EndSeal + 2 * Pitch'),(33,'Deflection','(Head - Neck) / 2 - Clearance'),(34,'ArmTop','(Neck - 2 * Taper - Slot) / 2'),(35,'FreeLift','Clearance * TaperHeight / Taper')]:
 sheet.set(f'A{row}',alias);sheet.set(f'B{row}','='+formula);sheet.setAlias(f'B{row}',alias);sheet.set(f'C{row}','ODVOZENO')
sheet.setColumnWidth('A',370);sheet.setColumnWidth('B',130);sheet.setColumnWidth('C',470)
doc.recompute()
def p(n):return 'Parameters.'+n
def exp(o,k,v):o.setExpression(k,v)

# Analytic common tangent between two circular shoulders. Native expressions
# avoid fragile edge-index dependencies during a dimensional recompute.
DERIVED = [
 ('Dy','Width - BackRadius - NoseRadius'),
 ('Dz','Height - BackRadius - NoseRadius'),
 ('D','sqrt(Dy * Dy + Dz * Dz)'),
 ('Alpha','(NoseRadius - BackRadius) / D'),
 ('Beta','sqrt(1 - Alpha * Alpha)'),
 ('Ny','Alpha * Dy / D - Beta * Dz / D'),
 ('Nz','Alpha * Dz / D + Beta * Dy / D'),
 ('Ty0','NoseRadius + Ny * NoseRadius'),
 ('Tz0','NoseRadius + Nz * NoseRadius'),
 ('Ty1','Width - BackRadius + Ny * BackRadius'),
 ('Tz1','Height - BackRadius + Nz * BackRadius'),
]
for row,(alias,formula) in enumerate(DERIVED,61):
    sheet.set(f'A{row}',alias);sheet.set(f'B{row}','='+formula);sheet.setAlias(f'B{row}',alias)
    sheet.set(f'C{row}','Odvozená tečna zaobleného profilu')
doc.recompute()
sk=doc.addObject('Sketcher::SketchObject','ProfileSketch')
sk.Label='Parametrické jádro náběhu mezi kruhovými rameny'
sk.Placement.Rotation=App.Rotation(App.Vector(0,1,0),App.Vector(0,0,1),App.Vector(1,0,0),'ZXY')
sk.Placement.Base=App.Vector(0,-1,1)
exp(sk,'Placement.Base.z',p('Bed')+' - 1 mm')
# Positive sketch coordinates (+1) make all coordinate constraints nonzero.
coords=[('0 mm','0 mm'),(p('Width'),'0 mm'),
        (p('Width'),p('Height')+' - '+p('BackRadius')),
        (p('Width')+' - '+p('BackRadius'),p('Height')+' - '+p('BackRadius')),
        (p('Ty1'),p('Tz1')),(p('Ty0'),p('Tz0')),
        (p('NoseRadius'),p('NoseRadius')),('0 mm',p('NoseRadius'))]
numeric=[(0,0),(20,0),(20,7),(17,7),(sheet.Ty1.Value,sheet.Tz1.Value),
         (sheet.Ty0.Value,sheet.Tz0.Value),(.5,.5),(0,.5)]
for i in range(len(coords)):
    a,b=numeric[i],numeric[(i+1)%len(coords)]
    sk.addGeometry(Part.LineSegment(App.Vector(a[0]+1,a[1]+1,0),App.Vector(b[0]+1,b[1]+1,0)),False)
for i in range(len(coords)):
    sk.addConstraint(Sketcher.Constraint('Coincident',i,2,(i+1)%len(coords),1))
    for axis,value,formula in zip(('DistanceX','DistanceY'),numeric[i],coords[i]):
        c=sk.addConstraint(Sketcher.Constraint(axis,i,1,float(value+1)))
        sk.setExpression(f'Constraints[{c}]','('+formula+') + 1 mm')
core=doc.addObject('Part::Extrusion','RampCore')
core.Base=sk;core.DirMode='Normal';core.Solid=True;exp(core,'LengthFwd',p('TotalLength'))
def cylinder(name,r,y,z):
    o=doc.addObject('Part::Cylinder',name)
    o.Placement.Rotation=App.Rotation(App.Vector(0,1,0),90)
    exp(o,'Radius',r);exp(o,'Height',p('TotalLength'))
    exp(o,'Placement.Base.y',y);exp(o,'Placement.Base.z',p('Bed')+' + ('+z+')')
    return o
nose=cylinder('RoundedNose',p('NoseRadius'),p('NoseRadius'),p('NoseRadius'))
back=cylinder('RoundedShoulder',p('BackRadius'),p('Width')+' - '+p('BackRadius'),p('Height')+' - '+p('BackRadius'))
rounded=doc.addObject('Part::MultiFuse','ContinuousProfile')
rounded.Shapes=[core,nose,back];rounded.Refine=True
doc.recompute()

def box(name,x,length,y,width,z=None,height=None):
 o=doc.addObject('Part::Box',name)
 for k,v in [('Length',length),('Width',width),('Height',height or p('Height')+' + 2 mm'),('Placement.Base.x',x),('Placement.Base.y',y),('Placement.Base.z',z or p('Bed')+' - 1 mm')]:exp(o,k,v)
 return o
def boolean(kind,name,a,b):
 o=doc.addObject('Part::'+kind,name);o.Base=a;o.Tool=b;o.Refine=True;return o
def fuse(name,items):
 o=doc.addObject('Part::MultiFuse',name);o.Shapes=items;o.Refine=True;return o
def num(expr):
 import re
 expr=re.sub(r'Parameters\.([A-Za-z0-9]+)',lambda m:str(getattr(sheet,m.group(1)).Value),expr)
 return eval(expr.replace(' mm',''),{'__builtins__':{}},{})
def polygon(name,coords,z):
 skp=doc.addObject('Sketcher::SketchObject',name);skp.Placement.Base=App.Vector(-100,-100,0);exp(skp,'Placement.Base.z',z)
 points=[(num(x)+100,num(y)+100) for x,y in coords]
 for i,(x,y) in enumerate(points):
  a=points[(i+1)%len(points)];skp.addGeometry(Part.LineSegment(App.Vector(x,y,0),App.Vector(a[0],a[1],0)),False)
 for i,(x,y) in enumerate(points):
  skp.addConstraint(Sketcher.Constraint('Coincident',i,2,(i+1)%len(points),1))
  for axis,v,expr in zip(('DistanceX','DistanceY'),(x,y),coords[i]):
   c=skp.addConstraint(Sketcher.Constraint(axis,i,1,v));exp(skp,f'Constraints[{c}]','100 mm + ('+expr+')')
 return skp

def latch_loft(name,joint,cavity=False):
 # Waisted keys: wide at base, narrowed at1.2mm, wide again at2.4mm. Capture both signs of Z.
 # Clearance is explicit in X/Y, not a claimed uniform normal offset on ramps.
 sections=[];c=p('Clearance') if cavity else '0 mm';J=p(joint)
 for level,(z,taper) in enumerate([(p('Bed')+' - 1 mm','0 mm'),(p('Bed'),'0 mm'),(p('Bed')+' + '+p('TaperHeight'),p('Taper')),(p('Bed')+' + 2 * '+p('TaperHeight'),'0 mm'),(p('Bed')+' + '+p('Height')+' + 1 mm','0 mm')]):
  n='('+p('Neck')+' / 2 - ('+taper+') + ('+c+'))'
  h='('+p('Head')+' / 2 - ('+taper+') + ('+c+'))'
  # Two square retaining faces (x=shoulder), long insertion ramps and split nose.
  R=p('RootRadius')
  arc=[]
  for k in range(9):
   angle=k*math.pi/16
   xx=f'{1-math.cos(angle):.12f} * '+R
   yy='-'+n+' - '+R+f' + {math.sin(angle):.12f} * '+R
   arc.append((xx,yy))
  xy=[('-1 mm','-'+n+' - '+R)]+arc+[
      (p('Shoulder')+' - ('+c+')','-'+n),
      (p('Shoulder')+' - ('+c+')','-'+h),(p('Shoulder')+' + 1 mm + ('+c+')','-'+h),
      (p('TipLength')+' + ('+c+')','-'+n),(p('TipLength')+' + ('+c+')',n),
      (p('Shoulder')+' + 1 mm + ('+c+')',h),(p('Shoulder')+' - ('+c+')',h),
      (p('Shoulder')+' - ('+c+')',n)]+[(x,'-('+y+')') for x,y in reversed(arc)]+[('-1 mm',n+' + '+R)]
  coords=[(J+' + ('+x+')',p('SnapY')+' + ('+y+')') for x,y in xy]
  sections.append(polygon(name+'Section'+str(level),coords,z))
 loft=doc.addObject('Part::Loft',name);loft.Sections=sections;loft.Solid=True;loft.Ruled=True;loft.Closed=False
 return loft

def round_slot(name,joint):
 J=p(joint)
 b=box(name+'Open',J+' - '+p('RootBack')+' + '+p('Slot')+' / 2',p('TipLength')+' + '+p('RootBack')+' + 1 mm',p('SnapY')+' - '+p('Slot')+' / 2',p('Slot'))
 o=doc.addObject('Part::Cylinder',name+'RoundRoot')
 for k,v in [('Radius',p('Slot')+' / 2'),('Height',p('Height')+' + 2 mm'),('Placement.Base.x',J+' - '+p('RootBack')+' + '+p('Slot')+' / 2'),('Placement.Base.y',p('SnapY')),('Placement.Base.z',p('Bed')+' - 1 mm')]:exp(o,k,v)
 return fuse(name,[b,o])

male=[];female=[];slots=[];guides=[];guideholes=[]
for i,joint in enumerate(('Joint1','Joint2'),1):
 male.append(latch_loft('MaleLatch'+str(i),joint));female.append(latch_loft('FemaleCavity'+str(i),joint,True));slots.append(round_slot('FlexSlot'+str(i),joint))
 guides.append(box('GuideTongue'+str(i),p(joint)+' - 1 mm',p('GuideLength')+' + 1 mm',p('GuideY'),p('GuideWidth')))
 guideholes.append(box('GuideSocket'+str(i),p(joint)+' - '+p('Clearance'),p('GuideLength')+' + 2 * '+p('Clearance'),p('GuideY')+' - '+p('Clearance'),p('GuideWidth')+' + 2 * '+p('Clearance')))
starts=[p('EndSeal'),p('Joint1'),p('Joint2')];ends=[p('Joint1'),p('Joint2'),p('TotalLength')+' - '+p('EndSeal')]
parts=[]
for i in range(3):
 mask=box('BodyMask'+str(i+1),starts[i],ends[i]+' - ('+starts[i]+')','0 mm',p('Width'))
 if i<2:
  mask=fuse('WithMale'+str(i+1),[mask,male[i],guides[i]])
  mask=boolean('Cut','SplitMale'+str(i+1),mask,slots[i])
 if i>0:
  mask=boolean('Cut','FemalePocket'+str(i+1),mask,female[i-1])
  mask=boolean('Cut','GuidePocket'+str(i+1),mask,guideholes[i-1])
 o=boolean('Common','Part'+str(i+1),rounded,mask);o.Label=f'Díl {i+1} — TPU snap575'
 o.addProperty('App::PropertyString','DesignStatus','Návrh');o.DesignStatus='Dvě západky XY + oboustranná rybina Z; fit, retence a těsnost neověřeny.'
 parts.append(o)
bed=box('AdhesiveBed','0 mm',p('TotalLength'),'0 mm',p('Width'),'0 mm',p('Bed'));bed.Label='Lepidlo pouze pod lištou — netisknout'
end1=boolean('Common','EndSeal1',rounded,box('EndMask1','0 mm',p('EndSeal'),'0 mm',p('Width')))
end2=boolean('Common','EndSeal2',rounded,box('EndMask2',p('TotalLength')+' - '+p('EndSeal'),p('EndSeal'),'0 mm',p('Width')))
end1.Label='Koncová rezerva2mm — netisknout';end2.Label=end1.Label
samples=[]
window=box('SampleWindow',p('Joint1')+' - 22 mm','62 mm','0 mm',p('Width'))
for i in range(2):
 o=boolean('Common','Sample'+str(i+1),parts[i],window);o.Label='Zkušební protikus '+str(i+1);samples.append(o)
doc.recompute()

def dims(s):
 b=s.BoundBox;return [b.XLength,b.YLength,b.ZLength]
def audit():
 invalid=[o.Name for o in doc.Objects if 'Invalid' in o.State];assert not invalid,invalid
 shapes=[o.Shape for o in parts]
 assert all(s.isValid() and len(s.Solids)==1 for s in shapes),[(s.isValid(),len(s.Solids)) for s in shapes]
 assert all(o.FullyConstrained for o in doc.Objects if o.TypeId=='Sketcher::SketchObject')
 overlaps=[shapes[i].common(shapes[j]).Volume for i in range(3) for j in range(i+1,3)];assert max(overlaps)<1e-6,overlaps
 assert max(s.BoundBox.YMax for s in shapes)<=sheet.Width.Value+1e-6
 assert min(s.BoundBox.YMin for s in shapes)>=-1e-6
 bodybox=Part.makeCompound(shapes).BoundBox
 assert abs(bodybox.XMin-sheet.EndSeal.Value)<1e-6
 assert abs(bodybox.XMax-(sheet.TotalLength.Value-sheet.EndSeal.Value))<1e-6
 assert abs(bodybox.ZLength-sheet.Height.Value)<1e-6
 contacts=[sum(f.Area for f in s.Faces if abs(f.BoundBox.ZMin-sheet.Bed.Value)<1e-7 and abs(f.BoundBox.ZMax-sheet.Bed.Value)<1e-7) for s in shapes]
 assert min(contacts)>100
 joints=[]
 for i in range(2):
  a,b=shapes[i],shapes[i+1]
  # Underformed rigid translations intentionally collide with retaining shoulders.
  trials=[]
  for label,vec in [('pull_apart_x',(-1,0,0)),('lift_male_z',(0,0,1)),('lift_female_z',(0,0,-1)),('side_y',(0,1,0)),('side_y_opposite',(0,-1,0))]:
   moved=a.copy();moved.translate(App.Vector(*vec));v=moved.common(b).Volume
   assert v>0.01,(i,label,v)
   trials.append({'direction':label,'translation_mm':list(vec),'interference_mm3':v})
  joints.append({'joint':i+1,'nominal_overlap_mm3':a.common(b).Volume,'rigid_retention_probes':trials})
 # Nonlinear TPU insertion/force is not solved; geometric lateral travel is computed.
 delta=sheet.Deflection.Value
 assert delta>0 and sheet.Slot.Value-2*delta>=0.6-1e-8
 assert sheet.ArmTop.Value>=1.0
 for o in samples:assert o.Shape.isValid() and len(o.Shape.Solids)==1
 return {'installed_envelope_mm':[sheet.TotalLength.Value,sheet.Width.Value,sheet.Height.Value+sheet.Bed.Value],
 'tpu_length_including_joints_mm':bodybox.XLength,'body_height_mm':sheet.Height.Value,'end_reserve_each_mm':sheet.EndSeal.Value,'bed_mm':sheet.Bed.Value,
 'part_bounds_mm':[dims(s) for s in shapes],'part_solid_counts':[len(s.Solids) for s in shapes],'parts_valid':True,'pair_overlap_mm3':overlaps,
 'bottom_contact_areas_mm2':contacts,'sample_bounds_mm':[dims(o.Shape) for o in samples],'joints':joints,
 'design_lateral_clearance_mm':sheet.Clearance.Value,'required_finger_deflection_each_mm':delta,'remaining_central_slot_at_squeeze_mm':sheet.Slot.Value-2*delta,
 'minimum_waist_arm_width_mm':sheet.ArmTop.Value,'nominal_geometric_z_play_mm':sheet.FreeLift.Value,'anti_lift_taper_each_mm':sheet.Taper.Value,
 'female_overhang_from_vertical_degrees':math.degrees(math.atan(sheet.Taper.Value/sheet.TaperHeight.Value)),
 'all_sketches_fully_constrained':True,'invalid_objects':invalid}
report={'status':'NÁVRH KE SCHVÁLENÍ — počítačová kontrola není fyzické ověření TPU snapu',
 'user_parameters_mm':{'length':575,'width_maximum':20,'preferred_installed_height_approx':10},'body_height_mm':8,'part_count':3,
 'design_parameters_mm':{n:v for n,_,v,_ in VALUES},'freecad_version':App.Version()[:3],
 'material_assumption':'Alzament TPU95A; barva/materiál uživatelových černých kusů neověřeny',
 'native_features_only':True,'insertion_direction':'female part moves -X toward male; fingers temporarily bend toward SnapY',
 'joint_adhesive':'none; no adhesive reference inside either mechanical joint'}
report['nominal']=audit();print('NOMINAL_OK',flush=True)
tests=[]
for changes in [{'TotalLength':600},{'Clearance':0.25,'Head':7.1},{'TaperHeight':1.4,'Slot':2.1}]:
 for key,val in changes.items():sheet.set(sheet.getCellFromAlias(key),f'{val} mm')
 doc.recompute();tests.append({'changes_mm':changes,'result':audit()})
 for key,_,val,_ in VALUES:sheet.set(sheet.getCellFromAlias(key),f'{val} mm')
 doc.recompute()
report['parameter_tests']=tests;report['nominal_after_restore']=audit()

def export(objects,folder,stem):
 records=[]
 for i,o in enumerate(objects,1):
  sh=o.Shape.copy();b=sh.BoundBox;origin=App.Vector(b.XMin,b.YMin,b.ZMin);sh.translate(-origin)
  mesh=MeshPart.meshFromShape(Shape=sh,LinearDeflection=0.01,AngularDeflection=0.08,Relative=False);assert mesh.isSolid()
  path=OUT/folder/f'{stem}-{i}.stl';mesh.write(str(path))
  regions=[]
  for k,J in enumerate((sheet.Joint1.Value,sheet.Joint2.Value),1):
   if b.XMin<=J+12<=b.XMax:
    for side in (-1,1):
     Y=sheet.SnapY.Value+side*sheet.Head.Value/2
     regions.append({'name':f'spoj{k}-zapadka{side:+d}','min_mm':[J+11-origin.x,Y-0.9-origin.y,0.2],'max_mm':[J+14-origin.x,Y+0.9-origin.y,3.0]})
  records.append({'file':str(path.relative_to(OUT)),'closed':True,'facets':mesh.CountFacets,'bounds_mm':dims(sh),'origin_min_mm':[0,0,0],
   'assembly_origin_mm':[origin.x,origin.y,origin.z],'retention_audit_regions':regions})
 return records
report['stl']=export(parts,'stl','dil');report['test_sample_stl']=export(samples,'vzorek','spoj')
report['sample_bounds_mm']=[dims(o.Shape) for o in samples]
if App.GuiUp:
 for o in doc.Objects:o.ViewObject.Visibility=o in parts+[bed,end1,end2]
doc.recompute();doc.saveAs(str(OUT/'prepazka-575-zacvak.FCStd'))
report['validation_pass']=True
(OUT/'kontrola-modelu.json').write_text(json.dumps(report,ensure_ascii=False,indent=2)+'\n')
print('SNAP575_GEOMETRY_OK '+json.dumps(report['nominal']),flush=True)
