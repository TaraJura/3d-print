# -*- coding: utf-8 -*-
"""Render real saved CAD with native FreeCAD GUI. Overwrites PNGs and GUI state.
Preview-only cropped/exploded objects are removed before saving final FCStd.
No ImageGen, slicing or printer operations.
"""
from pathlib import Path
import json
import FreeCAD as App
import FreeCADGui as Gui
import Part
from PySide import QtCore
from pivy import coin
OUT=Path(__file__).resolve().parent
report=json.loads((OUT/'kontrola-modelu.json').read_text())
assert report['validation_pass']
doc=App.openDocument(str(OUT/'prepazka-B.FCStd'))
doc.recompute()
parts=[doc.getObject('Part'+str(i)) for i in (1,2,3)]
view=Gui.activeDocument().activeView()
COLORS=[(.75,.78,.80),(.54,.62,.67),(.75,.78,.80)]
temp=[]
def style(o,c):
    v=o.ViewObject
    if 'ShapeAppearance' in v.PropertiesList:
        m=v.ShapeAppearance[0];m.DiffuseColor=c;v.ShapeAppearance=[m]
    v.ShapeColor=c;v.LineColor=(.15,.19,.22);v.LineWidth=1.3
    v.DisplayMode='Flat Lines'
def hide_all():
    for o in doc.Objects:
        if hasattr(o,'ViewObject'):o.ViewObject.Visibility=False
def full():
    hide_all()
    for o,c in zip(parts,COLORS):style(o,c);o.ViewObject.Visibility=True
def camera(eye,aspect=2.75):
    eye=App.Vector(*eye);up=App.Vector(0,0,1)
    view.setCameraType('Orthographic')
    rotation=App.Rotation(up.cross(eye),up,eye,'ZXY')
    shapes=[o.Shape for o in doc.Objects if hasattr(o,'Shape') and o.ViewObject.Visibility and not o.Shape.isNull()]
    bbox=Part.makeCompound(shapes).BoundBox
    corners=[App.Vector(x,y,z) for x in (bbox.XMin,bbox.XMax) for y in (bbox.YMin,bbox.YMax) for z in (bbox.ZMin,bbox.ZMax)]
    projected=[rotation.inverted().multVec(v-bbox.Center) for v in corners]
    dx=max(v.x for v in projected)-min(v.x for v in projected)
    dy=max(v.y for v in projected)-min(v.y for v in projected)
    node=view.getCameraOrientation() # initialize view before direct nonanimated camera update
    node=view.getCameraNode()
    node.orientation.setValue(rotation.Q)
    pos=bbox.Center+eye.normalize()*1000
    node.position.setValue(pos.x,pos.y,pos.z)
    node.height.setValue(max(dy,dx/aspect)*1.18)
    node.nearDistance.setValue(1);node.farDistance.setValue(3000)
    view.redraw();Gui.updateGui()
def preview(shape,name,color):
    o=doc.addObject('Part::Feature',name);o.Shape=shape;style(o,color);o.ViewObject.Visibility=True;temp.append(o)
    return o
def start():
    Gui.getMainWindow().resize(1800,700)
    full();camera((.18,-1,.85));QtCore.QTimer.singleShot(1000,save_full)
def save_full():
    view.saveImage(str(OUT/'sestava-cad.png'),2200,800,'White')
    hide_all();Gui.getMainWindow().resize(1400,950)
    pitch=doc.Parameters.Pitch.Value
    crop=Part.makeBox(80,40,30,App.Vector(pitch-40,-10,-5))
    for i in range(2):
        s=parts[i].Shape.common(crop)
        if i==1:s.translate(App.Vector(18,9,6))
        preview(s,'JointPreview'+str(i),COLORS[i])
    doc.recompute();camera((-.65,-1.2,1.4),1600/1100);QtCore.QTimer.singleShot(900,save_joint)
def save_joint():
    view.saveImage(str(OUT/'spoj-rozebrany-cad.png'),1600,1100,'White')
    for o in temp:doc.removeObject(o.Name)
    temp.clear();hide_all()
    # A short end sample of the actual nominal section, with no altered shape.
    sample=doc.ContinuousProfile.Shape.common(Part.makeBox(45,30,20,App.Vector(0,-5,-5)))
    preview(sample,'ProfilePreview',COLORS[0]);doc.recompute()
    camera((-1.6,-.8,.65),1.5);QtCore.QTimer.singleShot(900,save_profile)
def save_profile():
    view.saveImage(str(OUT/'profil-B-cad.png'),1500,1000,'White')
    for o in temp:doc.removeObject(o.Name)
    temp.clear();Gui.getMainWindow().resize(1800,700)
    full();camera((.18,-1,.85));doc.recompute();doc.save()
    file=doc.FileName;App.closeDocument(doc.Name)
    reopened=App.openDocument(file);reopened.recompute()
    visible=[o.Name for o in reopened.Objects if hasattr(o,'Shape') and o.ViewObject.Visibility]
    assert set(visible)=={'Part1','Part2','Part3'},visible
    invalid=[o.Name for o in reopened.Objects if 'Invalid' in o.State]
    assert not invalid,invalid
    # Native recompute with a changed length after reopening, then restore.
    reopened.Parameters.set('B2','600 mm');reopened.recompute()
    end=reopened.Part3.Shape.BoundBox.XMax
    assert abs(end-600)<1e-6,end
    reopened.Parameters.set('B2','570 mm');reopened.recompute()
    assert abs(reopened.Part3.Shape.BoundBox.XMax-570)<1e-6
    report['gui_validation']={'saved_reopened_and_recomputed':True,'visible_objects':visible,
      'parameter_change_after_reopen_mm':[600,570],'invalid_objects':invalid,
      'images':['sestava-cad.png','spoj-rozebrany-cad.png','profil-B-cad.png'],
      'preview_note':'Joint: cropped actual ends, right part translated +18x,+9y,+6z mm for explanation only'}
    (OUT/'kontrola-modelu.json').write_text(json.dumps(report,ensure_ascii=False,indent=2)+'\n')
    reopened.save();App.closeDocument(reopened.Name)
    print('BARRIER_RENDER_OK',flush=True);Gui.getMainWindow().close()
QtCore.QTimer.singleShot(900,start)
