# -*- coding: utf-8 -*-
"""Real CAD views of V05. Only presentation objects and visibility change; the Scabbard is never edited.
Wall, screw heads and the section cut are illustrations for these pictures only. The knife is the
hidden KnifeReference group. Saves the document so that only the final red Scabbard is visible.
"""
from pathlib import Path
import hashlib, json, os, traceback
import FreeCAD as App
import FreeCADGui as Gui
import Part
from PySide import QtCore
from pivy import coin  # loads the SWIG wrappers needed by view.getCameraNode()

OUT = Path(__file__).resolve().parent
RED = (.72, .05, .07)
# Any exception in this macro would leave the GUI waiting forever under Xvfb. Nothing is saved until finish().
QtCore.QTimer.singleShot(200000, lambda: os._exit(2))
App.ParamGet('User parameter:BaseApp/Preferences/Document').SetInt('CountBackupFiles', 0)
doc = App.openDocument(str(OUT / 'pouzdro.FCStd'))
doc.recompute()
body, par = doc.Scabbard, doc.Parameters
assert body.TypeId == 'PartDesign::Body'
original = body.Shape.Volume
knife = [doc.IllustrativeBlade, doc.IllustrativeNeck, doc.IllustrativeHandle]
view = Gui.activeDocument().activeView()


def style(o, color, lines=(.25, .0, .01), width=.6, mode='Flat Lines'):
    v = o.ViewObject
    v.ShapeColor = color
    v.DisplayMode = mode
    v.LineColor = lines
    v.LineWidth = width


body.ViewObject.DisplayModeBody = 'Tip'
style(body, RED)
for o in body.Group:
    if not o.TypeId.startswith('Sketcher'):
        style(o, RED)
style(knife[0], (.76, .80, .79), (.25, .28, .28))
style(knife[1], (.55, .60, .58), (.25, .28, .28))
style(knife[2], (.28, .17, .10), (.12, .07, .04))


def ref(name, label, shape, color, lines=(.45, .45, .42)):
    o = doc.addObject('Part::Feature', name)
    o.Label = label
    o.Shape = shape
    style(o, color, lines)
    return o


axis_y = par.BladeAxisFromWall.Value
wall = ref('IllustrativeWall', 'ILUSTRACE — stěna, materiál neznámý',
           Part.makeBox(900, 1, 900, App.Vector(-450, axis_y, -200)), (.95, .94, .91))
heads = []
front = par.WallFaceY.Value
for i, (x, z) in enumerate([(par.MountX.Value, par.MouthZ.Value + par.MountEdge.Value), (-par.MountX.Value, par.MountEdge.Value)]):
    head = Part.makeCylinder(5, 3, App.Vector(x, front - 3, z), App.Vector(0, 1, 0))
    heads.append(ref('IllustrativeScrew%d' % i, 'ILUSTRACE — hlava Ø10×3; skutečné vruty neznámé', head, (.52, .55, .53), (.2, .2, .2)))
context = doc.addObject('App::DocumentObjectGroup', 'VisualContext')
context.Label = 'ILUSTRACE — netisknout'
context.Group = [wall] + heads
# Section at X = 0 for one picture only; removed before saving.
half = Part.makeBox(400, 400, 900, App.Vector(0, -200, -200))
sect_body = ref('TmpSectionBody', 'tmp', body.Shape.cut(half), RED, (.25, .0, .01))
sect_knife = [ref('TmpSectionKnife%d' % i, 'tmp', o.Shape.cut(half), c, (.15, .15, .15))
              for i, (o, c) in enumerate(zip(knife, [(.76, .80, .79), (.55, .60, .58), (.28, .17, .10)]))]
sect_wall = ref('TmpSectionWall', 'tmp', wall.Shape.cut(half), (.95, .94, .91))
temporary = [sect_body, sect_wall] + sect_knife


def show(objs):
    for o in doc.Objects:
        if hasattr(o, 'ViewObject') and o.ViewObject and not o.TypeId.startswith('App::DocumentObjectGroup'):
            o.ViewObject.Visibility = o in objs
    doc.KnifeReference.ViewObject.Visibility = True
    context.ViewObject.Visibility = True
    for o in knife + [wall] + heads + temporary:
        o.ViewObject.Visibility = o in objs


def camera(eye, shapes, aspect, margin=1.06):
    eye, up = App.Vector(*eye), App.Vector(0, 0, 1)
    rot = App.Rotation(up.cross(eye), up, eye, 'ZXY')
    view.setCameraType('Orthographic')
    bb = Part.makeCompound(shapes).BoundBox
    corners = [App.Vector(x, y, z) for x in (bb.XMin, bb.XMax) for y in (bb.YMin, bb.YMax) for z in (bb.ZMin, bb.ZMax)]
    proj = [rot.inverted().multVec(v - bb.Center) for v in corners]
    dx = max(p.x for p in proj) - min(p.x for p in proj)
    dy = max(p.y for p in proj) - min(p.y for p in proj)
    view.getCameraOrientation()
    node = view.getCameraNode()
    node.orientation.setValue(rot.Q)
    pos = bb.Center + eye.normalize() * 1000
    node.position.setValue(pos.x, pos.y, pos.z)
    # A portrait viewport keeps the camera width, a landscape one keeps its height.
    node.height.setValue((max(dx, dy * aspect) if aspect < 1 else max(dy, dx / aspect)) * margin)
    node.nearDistance.setValue(1)
    node.farDistance.setValue(3000)
    view.redraw()
    Gui.updateGui()


mouth = par.MouthZ.Value
mouth_zone = Part.makeBox(84, 40, 34, App.Vector(-42, -12, mouth - 20))
whole_knife = [body.Shape] + [o.Shape for o in knife]
SHOTS = [
    ('nahled-cad-celo.png', [body], (0, -1, 0), [body.Shape], 900, 2300),
    ('nahled-cad-iso.png', [body, wall] + heads, (-.55, -1, .42), [body.Shape], 1300, 2300),
    ('nahled-cad-s-nozem.png', [body, wall] + heads + knife, (-.5, -1, .3), whole_knife, 1100, 2700),
    ('nahled-cad-rez.png', [sect_body, sect_wall] + sect_knife, (1, 0, 0), whole_knife, 800, 2700),
    ('nahled-cad-usti.png', [body], (-.25, -.55, 1), [mouth_zone], 1500, 1000),
    ('nahled-cad-zadni.png', [body], (.45, 1, .3), [body.Shape], 1000, 2100),
]
IMAGES = [s[0] for s in SHOTS]


def guarded(step):
    def run():
        try:
            step()
        except Exception:
            print('V05_RENDER_FAILED', flush=True)
            traceback.print_exc()
            os._exit(1)  # no unsaved-document dialog, nothing saved
    return run


def shoot(i=0):
    if i:
        name, _, _, _, w, h = SHOTS[i - 1]
        view.saveImage(str(OUT / name), w, h, 'White')
    if i == len(SHOTS):
        finish()
        return
    _, objs, eye, shapes, w, h = SHOTS[i]
    show(objs)
    camera(eye, shapes, w / h)
    QtCore.QTimer.singleShot(900, guarded(lambda: shoot(i + 1)))


def finish():
    for o in temporary:
        doc.removeObject(o.Name)
    temporary.clear()
    show([body])
    doc.KnifeReference.ViewObject.Visibility = False
    context.ViewObject.Visibility = False
    doc.recompute()
    assert abs(body.Shape.Volume - original) < 1e-6
    doc.save()
    path = doc.FileName
    App.closeDocument(doc.Name)
    d = App.openDocument(path)
    d.recompute()
    visible = [o.Name for o in d.Objects if hasattr(o, 'Shape') and o.ViewObject and o.ViewObject.Visibility]
    assert visible == ['Scabbard'], visible
    assert d.Scabbard.ViewObject.DisplayModeBody == 'Tip'
    sha = lambda f: hashlib.sha256((OUT / f).read_bytes()).hexdigest()
    report = json.loads((OUT / 'kontrola-modelu.json').read_text())
    report['gui_validation'] = {
        'saved_reopened': True, 'visible': visible, 'illustrations_hidden': True, 'images': IMAGES,
        'images_sha256': {f: sha(f) for f in IMAGES}, 'document_sha256_after_gui_save': sha('pouzdro.FCStd'),
    }
    (OUT / 'kontrola-modelu.json').write_text(json.dumps(report, ensure_ascii=False, indent=2) + '\n')
    print('V05_RENDER_OK', flush=True)
    os._exit(0)  # everything is saved; skip the close dialog of the Xvfb session


def start():
    Gui.getMainWindow().resize(1800, 1200)
    shoot(0)


QtCore.QTimer.singleShot(900, guarded(start))
