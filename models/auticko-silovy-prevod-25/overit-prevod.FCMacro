"""Skutečné solidy a pohyb. Výsledek pouze do místního kontrolního JSON."""
from pathlib import Path
import math,json,hashlib
from collections import Counter
import FreeCAD as App,Part
ROOT=Path(__file__).resolve().parent
D=App.openDocument(str(ROOT/'auticko-silovy-prevod-25.FCStd'));S=D.Parameters
R=json.loads((ROOT/'kontrola-modelu.json').read_text())
assert R['source_hashes']=={n:hashlib.sha256((ROOT/n).read_bytes()).hexdigest() for n in R['source_hashes']},'Source/export mismatch: regenerate before checking'
def param(n):
    q=getattr(S,n);return float(q.Value if hasattr(q,'Value') else q)
m=param('GearModule');pa=param('PressureAngle');smalladd=param('SmallAddendum');largeadd=param('LargeAddendum');ded=param('Dedendum')
def tip(z):return m*(z/2+(smalladd if z in (18,22) else largeadd))
compound_radial=(param('RunningBore')-param('FixedPinDiameter')+param('FixedSeatBore')-param('FixedPinDiameter'))/2
output_radial=(param('RearBearingBore')-param('RearAxleDiameter')+param('OutputBore')-param('RearAxleDiameter'))/2
motor_radial=float(D.MotorSaddleBore0.Radius.Value)-param('MotorDiameter')/2
shifts=[motor_radial+compound_radial,2*compound_radial,compound_radial+output_radial]
centres=[param('Stage'+str(i)) for i in (1,2,3)]
shaft_axial=1.5-1.3;compound_axial=.2;motor_axial=.4
output_axial=shaft_axial+param('CrossPinBore')-param('CrossPinDiameter')
R['fit_stack']={'compound_radial_mm':compound_radial,'output_radial_mm':output_radial,'motor_radial_mm':motor_radial,'relative_radial_approach_mm':shifts,'shaft_axial_mm':shaft_axial,'output_axial_mm':output_axial,'limit':'Součet nominálních CAD rozdílů, nikoli změřená vůle výtisku. Nezahrnuje naklopení nebo ohyb.'}
objects=[D.getObject(i['name']) for i in R['assembly_instances']]+[D.getObject(n) for n in R['references']]
def world(o):
    sh=o.Shape.copy()
    if o.Name.startswith(('AssemblySteeringWheel','AssemblyWheelClip')):
        sh.Placement=D.getObject('WheelCarrier'+o.Name[-1]).Placement.multiply(sh.Placement)
    if o.Name.startswith('AssemblyHornLock'):
        sh.Placement=D.HornLockCarrier.Placement.multiply(sh.Placement)
    return sh
assert Counter(i['part'] for i in R['assembly_instances'])==Counter({k:v['copies'] for k,v in R['parts'].items()})
def overlap(a,b):
    x,y=a.BoundBox,b.BoundBox
    if x.XMax<y.XMin or y.XMax<x.XMin or x.YMax<y.YMin or y.YMax<x.YMin or x.ZMax<y.ZMin or y.ZMax<x.ZMin:return 0
    return a.common(b).Volume
collisions=[];pairs=[]
for i,a in enumerate(objects):
    for b in objects[i+1:]:
        v=overlap(world(a),world(b));pairs.append({'a':a.Name,'b':b.Name,'overlap_mm3':v})
        if set((a.Name,b.Name))=={'ServoReference','AssemblyHornReference'}:v=0
        if v>1e-6:
            collisions.append(pairs[-1]);print('COLLISION',pairs[-1],flush=True)
R['assembly_pairs']=pairs;R['assembly_collisions']=collisions
(ROOT/'kontrola-modelu.json').write_text(json.dumps(R,ensure_ascii=False,indent=2)+'\n')
if collisions:raise RuntimeError('Assembly collisions '+str(len(collisions)))
print('PROGRESS assembly pairs clear',len(pairs),flush=True)
def turn(sh,x,angle):
    a=sh.copy();a.rotate(App.Vector(x,0,float(S.AxleHeight.Value)),App.Vector(0,1,0),angle);return a
xo,xb,xa,xp=map(float,[S.RearX.Value,S.BX.Value,S.AX.Value,S.MotorX.Value])
base=[D.AssemblyOutput.Shape.copy(),D.AssemblyB.Shape.copy(),D.AssemblyA.Shape.copy(),D.AssemblyPinion.Shape.copy()]
samples=[]
for i in range(65):
    a=i*(360/55)/64
    shapes=[turn(base[0],xo,a),turn(base[1],xb,-2.5*a),turn(base[2],xa,(25/3)*a),turn(base[3],xp,-25*a)]
    sample={'output_deg':a,'pairs':[]}
    for stage,(left,right,shift,zsmall,zlarge) in enumerate([(2,3,shifts[0],18,54),(1,2,shifts[1],18,60),(0,1,shifts[2],22,55)],1):
        for centre_tag,move in [('min',-shift),('nominal',0),('max',shift)]:
            distance=centres[stage-1]+move;angle=math.radians(pa)
            aw=math.acos(m*(zsmall+zlarge)/2*math.cos(angle)/distance)
            correction=math.degrees((math.tan(aw)-aw-math.tan(angle)+angle)*(zsmall+zlarge)/zsmall)
            for flank in (-1,0,1):
                smallshape=turn(shapes[right],[xo,xb,xa,xp][right],flank*correction);smallshape.translate(App.Vector(move,0,0))
                vol=overlap(shapes[left],smallshape)
                trial={'stage':stage,'centre':centre_tag,'distance_mm':distance,'flank':flank,'phase_correction_deg':flank*correction,'overlap_mm3':vol,'relative_radial_approach_mm':shift}
                sample['pairs'].append(trial)
                assert vol<1e-6,('Gear clash',a,trial)
    samples.append(sample)
    if i%8==0:print('PROGRESS gear angle',i,'/64',flush=True)
R['gear_motion']={'samples':samples,'rates_vs_output':[1,-2.5,25/3,-25],'minimum_centres_mm':[a-b for a,b in zip(centres,shifts)],'maximum_centres_mm':[a+b for a,b in zip(centres,shifts)],'loaded_flanks_included':True,'limit':'Vzorkované ideální těleso; radiální vůle započtena konzervativním přiblížením os, nikoli naklonění/deformace nebo tiskové chyby.'}
# Celé kruhové obálky včetně hřídelí a příčného klínku/pojistky.
sweeps=[]
for label,x,y,r,h in [('A54',xa,12,tip(54),8),('A18',xa,0,tip(18),8),('AHub',xa,-10,6.5,30),('B60',xb,-2,tip(60),12),('B22',xb,-16,tip(22),8),('BHub',xb,-20,7,30),('Output55',xo,-18,tip(55),12),('OutputHub',xo,-28,11,22),('CrossKeyAndClip',xo,-26.5,14.2,7),('Input',xp,14.5,tip(18),5)]:
    env=Part.makeCylinder(r+.01,h,App.Vector(x,y,28),App.Vector(0,1,0))
    for obj in (D.SteeringFrame,D.Deck,D.MotorBody,D.AssemblyRearAxle,D.AssemblyFixedPinA,D.AssemblyFixedPinB):
        # Vlastní díra v obálce pro nosnou osu, stále kontroluje celý ostatní hmotový prostor.
        test=env
        if obj.Name in ('AssemblyFixedPinA','AssemblyFixedPinB') and ((label.startswith('A') and obj.Name.endswith('A')) or (label.startswith('B') and obj.Name.endswith('B'))):continue
        if obj.Name=='AssemblyRearAxle' and label in ('Output55','OutputHub','CrossKeyAndClip'):continue
        if obj.Name=='MotorBody' and label=='Input':continue
        v=overlap(test,obj.Shape);sweeps.append({'moving':label,'fixed':obj.Name,'overlap_mm3':v});assert v<1e-6,sweeps[-1]
R['rotational_envelopes']=sweeps
# Axiální rozsahy včetně součtu vůlí obou děr příčného klínku.
ax=[]
for outshift,bshift,ashift,pshift in [(o,b,a,p) for o in (-output_axial,output_axial) for b in (-compound_axial,compound_axial) for a in (-compound_axial,compound_axial) for p in (0,motor_axial)]:
    moved=[]
    for sh,y in zip(base,(outshift,bshift,ashift,pshift)):
        q=sh.copy();q.translate(App.Vector(0,y,0));moved.append(q)
    vols=[overlap(moved[0],moved[1]),overlap(moved[1],moved[2]),overlap(moved[2],moved[3])]
    fixedmax=max(overlap(q,D.SteeringFrame.Shape) for q in moved)
    ax.append({'output_mm':outshift,'B_mm':bshift,'A_mm':ashift,'pinion_mm':pshift,'gear_pair_overlaps_mm3':vols,'frame_overlap_mm3':fixedmax});assert max(vols+[fixedmax])<1e-6,ax[-1]
R['axial_extremes']={'cases':ax,'stage3_minimum_full_width_margin_mm':2-output_axial-compound_axial,'stage1_minimum_contact_width_mm':4.9,'explanation':'Výstupní rozsah = šířka drážky minus tloušťka klipu + průměr klínkové díry minus průměr klínku (vůle obou děr). B/A ±0,2; motor/pastorek0..+0,4.'}
# Skutečná šířka hlav z CAD kruhových hran, nikoli pouze analytický odhad.
tips=[]
for name,z,coeff in [('Input18Outline',18,smalladd),('A18Outline',18,smalladd),('B22Outline',22,smalladd),('A54Outline',54,largeadd),('B60Outline',60,largeadd),('Output55Outline',55,largeadd)]:
    ra=m*(z/2+coeff);chords=[]
    circles=[e for e in D.getObject(name).Shape.Edges if type(e.Curve).__name__=='Circle']
    max_radius=max(e.Curve.Radius for e in circles)
    selected=[e for e in circles if abs(e.Curve.Radius-max_radius)<1e-6]
    for edge in selected:
        vv=edge.Vertexes;assert len(vv)==2
        chords.append((vv[0].Point-vv[1].Point).Length)
    assert len(chords)==z,(name,len(chords),z)
    tips.append({'outline':name,'teeth':z,'actual_tip_edges':len(chords),'minimum_chord_mm':min(chords),'maximum_chord_mm':max(chords),'nominal_addendum_radius_mm':ra,'actual_curve_radius_mm':max_radius,'maximum_vertex_radial_mm':max(v.Point.Length for e in selected for v in e.Vertexes)})
assert min(v['minimum_chord_mm'] for v in tips)>.55
contact=[]
for (z1,z2),a,shift in zip([(18,54),(18,60),(22,55)],centres,shifts):
    distance=a+shift;rb1=m*z1/2*math.cos(math.radians(pa));rb2=m*z2/2*math.cos(math.radians(pa));ra1=tip(z1);ra2=tip(z2)
    aw=math.acos((rb1+rb2)/distance);eps=(math.sqrt(ra1*ra1-rb1*rb1)+math.sqrt(ra2*ra2-rb2*rb2)-distance*math.sin(aw))/(math.pi*m*math.cos(math.radians(pa)))
    contact.append({'teeth':[z1,z2],'maximum_centre_mm':distance,'ideal_contact_ratio':eps})
R['gear_profile']={'module_mm':m,'pressure_angle_deg':pa,'small_addendum':smalladd,'large_addendum':largeadd,'dedendum':ded,'profile_shift':param('ProfileShift'),'maximum_centre_contact_ratio':contact,'actual_tip_measurements':tips,'limit':'Šířka hlav měřena na skutečných CAD hranách; záběr u báze/filletu kontrolován skutečnými solidy v65 vzorcích fáze. Analytický kontaktní poměr nenahrazuje fyzickou zkoušku tisku.'}
assert min(c['ideal_contact_ratio'] for c in contact)>1.1,('Insufficient maximum-centre contact ratio',contact)
R['gear_validation_pass']=True
R['validation_pass']=False # Souhrn všech kontrol provede teprve uzavrit-kontroly.py.
(ROOT/'kontrola-modelu.json').write_text(json.dumps(R,ensure_ascii=False,indent=2)+'\n')
print('VALIDATION_COMPLETE',flush=True)
